module ted {
  yang-version 1;
  namespace "urn:TBD:params:xml:ns:yang:network:ted";
  // replace with IANA namespace when assigned
  prefix ted;

  import ietf-inet-types {
    prefix "inet";
  }

  organization "TBD";
  contact
    "TBD";
  description
    "Helper module to hold trafic engineering attributes for 
     any topology on which trafic engineering is enabled.";
  
  revision 2014-11-02 {
    description
      "Initial revision";
    reference 
      "RFC 4220: Traffic Engineering Link Management Information
      Base.
      RFC 6825: Traffic Engineering Database Management Information
      Base in Support of MPLS-TE/GMPLS.
      RFC 4802: Generalized Multiprotocol Label Switching (GMPLS)
      Traffic Engineering Management Information Base";
  }

  feature te-performance-metric {
    description
      "This feature indicates that the device supports
      TE performance metric defined in
      draft-ietf-ospf-te-metric-extensions.";
  }

  typedef switching-capabilities {
    type enumeration {
      enum "psc-1" {        
        value 1;
        description
          "Packet-Switch Capable-1 (PSC-1)";
      }
      enum "evpl" {
        value 30;
        description
          "Ethernet Virtual Private Line (EVPL)";
      }
      enum "l2sc" {
        value 51;
        description
          "Layer-2 Switch Capable (L2SC)";
      }
      enum "tdm" {
        value 100;
        description
          "Time-Division-Multiplex Capable (TDM)";
      }
      enum "otn-tdm" {
        value 110;
        description
          "OTN-TDM Capable";
      }
      enum "lsc" {
        value 150;
        description
          "Lambda-Switch Capable (LSC)";
      }
      enum "fsc" {
        value 200;
        description
          "Fiber-Switch Capable (FSC)";
      }
    }
    description
      "Switching Capabilities of an interface.";
    reference
      "RFC 5307: IS-IS Extensions in Support of Generalized
       Multi-Protocol Label Switching (GMPLS).
       RFC 3812: Multiprotocol Label Switching (MPLS) Traffic 
       Engineering (TE) Management Information Base (MIB).
       RFC 7074: Revised Definition of the GMPLS Switching Capability
       and Type Fields.
       RFC 7138: Traffic Engineering Extensions to OSPF
       for GMPLS Control of Evolving G.709 Optical Transport
       Networks.
       RFC 7139: GMPLS Signaling Extensions for Control of Evolving 
       G.709 Optical Transport Networks.";
  }

  typedef encoding-type {
    type enumeration {
      enum "not-gmpls" {        
        value 0;
        description
          "GMPLS is not in use";
      }
      enum "packet" {        
        value 1;
        description
          "Packet";
      }
      enum "ethernet" {        
        value 2;
        description
          "Ethernet";
      }
      enum "pdh" {        
        value 3;
        description
          "PDH";
      }
      enum "sdh-sonet" {        
        value 5;
        description
          "SDH or SONET";
      }
      enum "digital-wrapper" {        
        value 7;
        description
          "Digital Wrapper";
      }
      enum "lambda" {        
        value 8;
        description
          "Lambda";
      }
      enum "fiber" {        
        value 9;
        description
          "Fiber";
      }
      enum "fiber-channel" {        
        value 11;
        description
          "Fiber Channel";
      }
      enum "oduk" {        
        value 12;
        description
          "G.709 OKUk (Digital Path)";
      }
      enum "optical-channel" {        
        value 13;
        description
          "G.709 Optical Channel";
      }
    }
    description
      "Encoding type of an interface.";
    reference
      "RFC 3471: Generalized Multi-Protocol Label Switching (GMPLS)
       Signaling Functional Description.
       RFC 4328: Generalized Multi-Protocol Label Switching (GMPLS)
       Signaling Extensions for G.709 Optical Transport Networks
       Control.";
  }

  typedef pcc-capabilities {
    type bits {
      bit path-computation-with-gmpls-link-constraints {
        position 0;
        description "Link constraints";
      }
      bit bidirectional-path-computation {
        position 1;
        description "Bidirectional";
      }
      bit diverse-path-computation {
        position 2;
        description "Diverse";
      }
      bit load-balanced-path-computation {
        position 3;
        description "Load balanced";
      }
      bit synchronized-path-computation {
        position 4;
        description "Synchronized";
      }
      bit support-for-multiple-objective-functions {
        position 5;
        description "Multiple objective functions";
      }
      bit support-for-additive-path-constraints {
        position 6;
        description "Additive path constraints";
      }
      bit support-for-request-prioritization {
        position 7;
        description "Request prioritization";
      }
      bit support-for-multiple-requests-per-message {
        position 8;
        description "Multiple requests per message";
      }
    }
    description
      "Path Computation Capabilities.";
    reference
      "RFC 5088, draft-ietf-pce-disco-protoc-isis-07.txt
       OSPF/ISIS Protocol Extensions for Path Computation Element
       (PCE) Discovery.";
  }

  typedef performance-metric-normality {
    type enumeration {
      enum "unkown" {        
        value 0;
        description
          "Unkown";
      }
      enum "normal" {        
        value 1;
        description
          "Noarmal";
      }
      enum "abnormal" {        
        value 2;
        description
          "Abnormal. The anomalous bit is set.";
      }
    }
    description
      "Indicates whether a performance metric is normal, abnormal, or
      unkown.";
  }

  grouping performance-metric-attributes {
    description
      "Link performance information in real time.";
    reference 
      "draft-ietf-ospf-te-metric-extensions.";
    leaf unidirectional-delay {
      type uint32 {
        range 0..16777215;
      }
      description "Delay or latency in micro seconds.";
    }
    leaf unidirectional-min-delay {
      type uint32 {
        range 0..16777215;
      }
      description "Minimum delay or latency in micro seconds.";
    }
    leaf unidirectional-max-delay {
      type uint32 {
        range 0..16777215;
      }
      description "Maximum delay or latency in micro seconds.";
    }
    leaf unidirectional-delay-variation {
      type uint32 {
        range 0..16777215;
      }
      description "Delay variation in micro seconds.";
    }
    leaf unidirectional-packet-loss {
      type decimal64 {
        fraction-digits 6;
        range "0 .. 50.331642";
      }
      description 
        "Packet loss as a percentage of the total traffic sent
        over a configurable interval. The finest precision is
        0.000003%.";
    }
    leaf unidirectional-residual-bandwidth {
      type decimal64 {
        fraction-digits 2;
      }
      description 
        "Residual bandwidth that subtracts tunnel
        reservations from Maximum Bandwidth (or link capacity)
        [RFC3630] and provides an aggregated remainder across QoS
        classes.";
    }
    leaf unidirectional-available-bandwidth {
      type decimal64 {
        fraction-digits 2;
      }
      description 
        "Available bandwidth that is defined to be residual
        bandwidth minus the measured bandwidth used for the
        actual forwarding of non-RSVP-TE LSP packets.  For a
        bundled link, available bandwidth is defined to be the
        sum of the component link available bandwidths.";
    }
    leaf unidirectional-utilized-bandwidth {
      type decimal64 {
        fraction-digits 2;
      }
      description
        "Bandwidth utilization that represents the actual
        utilization of the link (i.e. as measured in the router).
        For a bundled link, bandwidth utilization is defined to
        be the sum of the component link bandwidth
        utilizations.";
    }
  }

  grouping performance-metric-normality-attributes {
    description
      "Link performance metric normality attributes.";
    reference 
      "draft-ietf-ospf-te-metric-extensions.";
    leaf unidirectional-delay {
      type performance-metric-normality;
      description "Delay normality.";
    }
    leaf unidirectional-min-delay {
      type performance-metric-normality;
      description "Minimum delay or latency normality.";
    }
    leaf unidirectional-max-delay {
      type performance-metric-normality;
      description "Maximum delay or latency normality.";
    }
    leaf unidirectional-delay-variation {
      type performance-metric-normality;
      description "Delay variation normality.";
    }
    leaf unidirectional-packet-loss {
      type performance-metric-normality;
      description "Packet loss normality.";
    }
    leaf unidirectional-residual-bandwidth {
      type performance-metric-normality;
      description "Residual bandwidth normality.";
    }
    leaf unidirectional-available-bandwidth {
      type performance-metric-normality;
      description "Available bandwidth normality.";
    }
    leaf unidirectional-utilized-bandwidth {
      type performance-metric-normality;
      description "Bandwidth utilization normality.";
    }
  }

  grouping ted-node-attributes {
    description
      "Identifier to uniquely identify a node in TED";
    reference 
      "RFC 5305, RFC 6119: IPv6 Traffic Engineering in IS-IS/OSPF";
    leaf te-router-id-ipv4 {
      type inet:ipv4-address;
      description
        "Globally unique IPv4 Traffic Engineering Router ID.";
    }
    leaf te-router-id-ipv6 {
      type inet:ipv6-address;
      description
        "Globally unique IPv6 Traffic Engineering Router ID";
    }
    list ipv4-local-address {
      key "ipv4-prefix";
      description
        "List of IPv4 Local Address(OSPF). RFC 5786";
      
      leaf ipv4-prefix {
        type inet:ipv4-prefix;
        description
          "Local IPv4 address for the node";
      }
    }
    list ipv6-local-address {
      key "ipv6-prefix";
      description
        "List of IPv6 Local Address.";
      reference
        "RFC 5786: Advertising a Router's Local Addresses
         in OSPF Traffic Engineering (TE) Extensions";
      leaf ipv6-prefix {
        type inet:ipv6-prefix;
        description
          "Local IPv6 address for the node";
      }
      leaf prefix-option {
        type uint8;
        description
          "IPv6 prefix option.";
      }
    }
    leaf pcc-capabilities {
      type pcc-capabilities;
      description
        "OSPF/ISIS PCC capabilities";
    }
  }

  grouping ted-link-info-attributes {
    description
      "Advertised TE informaton attributes.";
    leaf information-source {
      type enumeration {
        enum "unknown" {
          description "The source is unknown";
        }
        enum "locally-configured" {
          description "Configured TE link";
        }
        enum "ospfv2" {
          description "OSPFv2";
        }
        enum "ospfv3" {
          description "OSPFv3";
        }
        enum "isis" {
          description "ISIS";
        }
        enum "other" {
          description "Other source";
        }
      }
      description 
        "Indicates the source of the information about the link";
    }
    leaf credibility-preference {
      type uint16;
      description
        "The preference value to calculate the traffic engineering 
        database credibility value used for tie-break selection
        between different information-source values.
        Higher value is more preferable.";
    }
    leaf link-index {
      type uint64;
      description
        "The link identifier.  If OSPF is used, this represents an
        ospfLsdbID.  If IS-IS is used, this represents an isisLSPID.
        If a locally configured link is used, this object represents
        an unique value, which is locally defined in a router.";
    }
    list administrative-group {
      key "sequence";
      description
        "Administrative group or color of the link. 
        This attribute covers both administrative group (defined in
        RFC3630, RFC5329, and RFC5305), and extended administrative
        group (defined in RFC7308).";
      leaf sequence {
        type uint32;
        description
          "Sequence number of a 4-byte element of extended
          administrative group, indicating the position of these 
          bits.
          When sequence is 0, the element also represents the 
          non-extended 4-byte administrative group defined in
          RFC3630, RFC5329, and RFC5305.";
      }
      leaf ag-element {
        type uint32;
        description
          "4-byte element of extended administrative group.
          When sequence is 0, this attribute also represents the 
          non-extended 4-byte administrative group.";
      }
    }
    leaf max-link-bandwidth {
      type decimal64 {
        fraction-digits 2;
      }
      description
        "Maximum bandwidth that can be see on this link in this
        direction. Units in bytes per second";
    }
    leaf max-resv-link-bandwidth {
      type decimal64 {
        fraction-digits 2;
      }
      description
        "Maximum amount of bandwidth that can be reserved in this
         direction in this link. Units in bytes per second";
    }
    list unreserved-bandwidth {
      key "priority";
      max-elements "8";
      description
        "Unreserved bandwidth for 0-7 priority levels. Units in
        bytes per second";
      leaf priority {
        type uint8 {
          range "0..7";
        }
        description "Priority";
      }
      leaf bandwidth {
        type decimal64 {
          fraction-digits 2;
        }
        description
          "Unreserved bandwidth for this level";
      }
    }
    leaf te-default-metric {
      type uint32;
      description
        "Traffic Engineering Metric";
    }
    container performance-metric {
      if-feature te-performance-metric;
      description
        "Link performance information in real time.";
      reference 
        "draft-ietf-ospf-te-metric-extensions.";
      container measurement {
        description
          "Messured performance metric values. Static configuration
          and manual override of these measurements are also 
          allowed.";
        uses performance-metric-attributes;
      }
      container normality
      {
        description
          "Performance metric normality values.";
        uses performance-metric-normality-attributes;
      }
    }
    leaf link-protection-type {
      type enumeration {
        enum "unprotected" {
          description "unprotected";
        }
        enum "extra-traffic" {
          description "Extra traffic";
        }
        enum "shared" {
          description "Shared";
        }
        enum "1-for-1" {
          description "One for one protection";
        }
        enum "1-plus-1" {
          description "One plus one protection";
        }
        enum "enhanced" {
          description "Enhanced protection";
        }
      }
      description
        "Link Protection Type desired for this link";
    }
    list interface-switching-capabilities {
      key "switching-capability";
      description
        "List of interface capabilities for this interface";
      leaf switching-capability {
        type ted:switching-capabilities;        
        description
          "Switching Capability for this interface";
      }
      leaf encoding {
        type ted:encoding-type;
        description
          "Encoding supported by this interface";
      }
      list max-lsp-bandwidth {
        key "priority";
        max-elements "8";
        description
          "Maximum LSP Bandwidth at priorities 0-7";
        leaf priority {
          type uint8 {
            range "0..7";
          }
          description "Priority";
        }
        leaf bandwidth {
          type decimal64 {
            fraction-digits 2;
          }
          description
            "Max LSP Bandwidth for this level";
        }
      }
      container packet-switch-capable {
        when "../switching-capability = PSC-1  or "
          +"../switching-capability = PSC-2 or "
          +"../switching-capability = PSC-3 or "
          +"../switching-capability = PSC-4" {
          description "Valid only for PSC";
        }
        description
          "Interface has packet-switching capabilities";
        leaf minimum-lsp-bandwidth {
          type decimal64 {
            fraction-digits 2;
          }
          description
            "Minimum LSP Bandwidth. Units in bytes per second";
        }
        leaf interface-mtu {
          type uint16;
          description
            "Interface MTU";
        }
      }
      container time-division-multiplex-capable {
        when "../switching-capability = TDM" {
          description "Valid only for TDM";
        }
        description
          "Interface has time-division multiplex capabilities";

        leaf minimum-lsp-bandwidth {
          type decimal64 {
            fraction-digits 2;
          }
          description
            "Minimum LSP Bandwidth. Units in bytes per second";
        }
        leaf indication {
          type enumeration {
            enum "standard" {
              description "Indicates support of standard SONET/SDH";
            }
            enum "arbitrary" {
              description "Indicates support of arbitrary SONET/SDH";
            }
          }
          description
            "Indication whether the interface supports Standard or
             Arbitrary SONET/SDH";
        }
      }
    }
    container srlg {
      description
        "Shared Risk Link Group Attributes";
      uses srlg-attributes;
    }
  }

  grouping ted-link-attributes {
    description
      "TED Attributes associated with the link.";
    reference 
      "RFC 3630, RFC 3784: IS-IS / OSPF Traffic Engineering (TE)";
    leaf admin-status {
      type enumeration {
        enum up {
          value 1;
          description
            "Enabled.";
        }
        enum down {
          value 2;
          description
            "Disabled.";
        }
        enum testing {
          value 3;
          description
            "In some test mode.";
        }
        }
      description
        "The desired state of the link.";
      }
    leaf oper-status {
      type enumeration {
        enum up {
          value 1;
          description
            "Operational up";
        }
        enum down {
          value 2;
          description
            "Operational down.";
        }
        enum testing {
          value 3;
          description
            "In some test mode";
        }
        enum unknown {
          value 4;
          description
            "Status cannot be determined for some reason.";
        }
      }
      description
        "The current operational state of the link.";
    }
    leaf area-id {
      type binary {
        length 1..13;
      }
      description
        "This object indicates the area identifier of the IGP. 
        If OSPF is used to advertise LSA, this represents an 
        ospfArea. If IS-IS is used, this represents an area address.
        Otherwise, this is zero.";
    }
    container performance-metric-throttle {
      if-feature te-performance-metric;
      description
        "Link performance information in real time.";
      reference 
        "draft-ietf-ospf-te-metric-extensions.";
      leaf unidirectional-delay-offset {
        type uint32 {
          range 0..16777215;
        }
        description 
          "Offset value to be added to the measured delay value.";
      }
      leaf measure-interval {
        type uint32;
        default 30;
        description 
          "Interval in seconds to measure the extended metric
          values.";
      }
      leaf advertisement-interval {
        type uint32;
        description 
          "Interval in seconds to advertise the extended metric
          values.";
      }
      leaf suppression-interval {
        type uint32 {
          range "1 .. max";
        }
        must "suppression-interval >= ../measure-interval" {
          error-message 
            "suppression-interval cannot be less then 
            measure-interval";
          description
            "Contraint on suppression-interval and 
            measure-interval.";
        }
        default 120;
        description 
          "Interval in seconds to suppress advertising the extended
          metric values.";
      }
      container threshold-out {
        uses performance-metric-attributes;
        description
          "If the measured parameter falls outside an upper bound
          for all but the min delay metric (or lower bound for
          min-delay metric only) and the advertised value is not
          already outside that bound, anomalous announcement will be
          triggered.";
      }
      container threshold-in {
        uses performance-metric-attributes;
        description
          "If the measured parameter falls inside an upper bound
          for all but the min delay metric (or lower bound for
          min-delay metric only) and the advertised value is not
          already inside that bound, normal (anomalous-flag cleared)
          announcement will be triggered.";
      }
      container threshold-accelerated-advertisement {
        description
          "Whe the difference between the last advertised value and
          current measured value exceed this threshold, anomalous
          announcement will be triggered.";
        uses performance-metric-attributes;
      }
    }
    uses ted-link-info-attributes;
    list alt-information-sources {
      key "information-source";
      description
        "A list of information sources learned but not used.";
      uses ted-link-info-attributes;
    }
  }
  
  grouping srlg-attributes {
    description
      "Shared Risk Link Group Attributes";
    reference
      "RFC 5307, RFC 4203: ISIS / OSPF Extensions in Support of
       Generalized Multi-Protocol Label Switching (GMPLS)";
    list srlg-values {
      key "srlg-value";
      description
        "List of Shared Risk Link Group this interface belongs to.";
      leaf srlg-value {
        type uint32;
        description
          "Shared Risk Link Group value";
      }
    }
  }
}
